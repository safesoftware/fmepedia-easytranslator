FME workspace EasyTranslator.fmw
Title: Generic format translator

Parameters:
- SourceDataset_GENERIC =   # Source File
- SourceFormat = GUESS_FROM_EXTENSION
- COORDSYS =   # COORDSYS Input Coordinate System
- GENERIC_OUT_BASE_NAME_GENERIC = translated_data   # Destination Filename
- DestinationFormat = ACAD
- COORDSYS_Dest =   # Output Coordinate System

Readers:
- GENERIC_1: GENERIC from $(SourceDataset_GENERIC) in $(COORDSYS)

Writers:
- GENERIC_2: GENERIC to C:/ProgramData/Safe Software/FME Server/DefaultResults in $(COORDSYS_Dest)

Bookmark: Generic Reader
Note: The Generic Reader allows you to specify / a file to read as well as the format or it will / attempt to guess the format used by the file.
Note: This reader feature type's Merge Parameters / are configured so that all feature types send / their features through this feature type / regardless of name.
FeatureTypeName (reader GENERIC_1)
    attributes: FNODE_ decimal(11,0), TNODE_ decimal(11,0), LPOLY_ decimal(11,0), RPOLY_ decimal(11,0), LENGTH decimal(18,5), AIRPORTS_ decimal(11,0), AIRPORTS_I decimal(11,0), LINE decimal(11,0), ADD_DATE varchar(11), NBTS decimal(11,0), FILLCHAR varchar(1), NAME varchar(12)
    -> DYNAMIC (writer GENERIC_2)

Bookmark: Generic Writer
Note: The Generic Writer allows you to specify an / output format for the destination file.
Note: This writer feature type's Dynamic Parameters are / configured so that at run time the feature type's / schema is determined from the source file.
DYNAMIC (writer GENERIC_2)
