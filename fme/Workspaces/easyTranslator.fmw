FME workspace easyTranslator.fmw
Title: Generic format translator

Parameters:
- COORDSYS =
- COORDSYS_Dest =
- DestinationFormat =
- GENERIC_OUT_BASE_NAME_GENERIC =
- SourceDataset_GENERIC =
- SourceFormat =

Readers:
- GENERIC_1: GENERIC from $(SourceDataset_GENERIC) in $(COORDSYS)
- CSV2_1: CSV2 from /DrinkingFountains.csv
- ACAD_1: ACAD from StreetLighting.dwg
- GEOJSON_1: GEOJSON from Zones.json
- GML_1: GML
- IGDS_1: IGDS from StreetLightingDGN.dgn
- MITAB_1: MITAB from Parks.tab
- OGCKML_1: OGCKML from /LocalAreas.kml
- SHAPEFILE_1: SHAPEFILE from VancouverLandBoundary.shp

Writers:
- GENERIC_2: GENERIC to /data/fmeserver/resources/system/temp/engineresults in $(COORDSYS_Dest)

Bookmark: Generic Reader
Note: The Generic Reader allows you to specify / a file to read as well as the format or it will / attempt to guess the format used by the file.
Note: This reader feature type's Merge Parameters / are configured so that all feature types send / their features through this feature type / regardless of name.
FeatureTypeName (reader GENERIC_1)
    attributes: FNODE_ decimal(11,0), TNODE_ decimal(11,0), LPOLY_ decimal(11,0), RPOLY_ decimal(11,0), LENGTH decimal(18,5), AIRPORTS_ decimal(11,0), AIRPORTS_I decimal(11,0), LINE decimal(11,0), ADD_DATE varchar(11), NBTS decimal(11,0), FILLCHAR varchar(1), NAME varchar(12)
    -> DYNAMIC (writer GENERIC_2)

Bookmark: Generic Writer
Note: The Generic Writer allows you to specify an / output format for the destination file.
Note: This writer feature type's Dynamic Parameters are / configured so that at run time the feature type's / schema is determined from the source file.
DYNAMIC (writer GENERIC_2)
